# 【内部仕様書】モータ

## 【内部仕様書】モータ: 【内部仕様書】モータ.docx への参照 (Container)
Microsoft Word ドキュメントへの読み取り専用の参照です。

### 更新履歴 (Functional)
更新履歴
| NO | 仕様書NO | 内容 | 日付 | 変更者 |
| --- | --- | --- | --- | --- |
| 1 | IS-Motor-01 | 初版発行 | 2019/6/24 | PMWG |
| 2 |  |  |  |  |
| 3 |  |  |  |  |
| 4 |  |  |  |  |
目次
更新履歴... 2
1. はじめに... 5
2. 全般... 6
2.1 名称... 6
2.2 用途... 6
2.3 一般情報... 6
2.4 納品物一覧... 6
3 モデル要件... 7
3.1 接続するモデリングツールやバージョン... 7
3.2 動作環境... 7
3.3 シミュレーション設定（Configuration Parameter ）... 7
3.4 見積計算速度... 7
3.5 モデル秘匿化... 7
3.6 参考ガイドライン... 7
4 要求機能と実現方法... 8
4.1 モデル化対象範囲... 8
4.2 モデル要求機能... 8
4.3 機能実現方法... 9
4.4 モデル外観イメージ... 10
4.5 入出力信号及びパラメータ仕様... 10
4.5.1 ノード... 10
4.5.2 モニタ変数... 10
4.5.3 入力... 10
4.5.4 出力... 11
4.5.5 パラメータ... 11
4.5.6 データ型... 11
4.6 動作保証範囲... 11
4.7 その他関連情報... 11
5 検証... 11
5.1 検証シナリオと判断基準... 11
5.2 検証結果... 11
6 サポート要件... 12
6.1 サポート内容... 12
6.2 サポート期間... 12
6.3 問合せ先... 12
1. はじめに
このドキュメントはOEMとサプライヤ間や1次サプライヤと2次サプライヤ間で行われるモデル流通プロセスに活用される内部仕様書である。
本ドキュメントで想定するモデル流通プロセスは以下である。
|  |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 |
| --- | --- |
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|  |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 |
| --- | --- |
【補足】納品チェック後に仕様間違いが発覚した場合は、再度プロセスを回す
図1．モデル流通プロセス

### 2. 全般: 全般 (Functional)
2. 全般
1
2
2.1 名称
パラレルハイブリッド駆動用モータ・ジェネレータモデル
2.2 用途
使用プロセス
車両モデルへ組み込み、燃費シミュレーションに用いる。
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 図2．適用Vプロセス
 用途
他モデルと結合し、車両レベルの燃費計算に使用する。
2.3 一般情報
本モデルが組込まれる車両情報を以下に記載する。
 車種：ガソリンコンベ車
 形態：乗用車
 セグメント：C（中型車、エンジン排気量1800 cc）
 ボディタイプ：ミドルセダン
 駆動方式：2WD（FF）
2.4 納品物一覧
納品予定物を以下に記載する。
 実行可能なシミュレーションモデル一式
 実行手順書
 検証結果ファイル
 モデル解説書

### 3 モデル要件: モデル要件 (Functional)
3 モデル要件
3.1 接続するモデリングツールやバージョン
 ツール名：MATLAB/Simulink, Simscape
 バージョン：R2018a
3.2 動作環境
1
2
2.1
2.2
＜MILS＞
使用予定PC仕様
CPU：Core-i7（第8世代）-2.4 GHz、RAM：16 GB
OS：Windows10-Pro, 64 bit
コンパイラ：MinGW5.3もしくはVisual Studio pro 2018
3.3 シミュレーション設定（Configuration Parameter ）
ソルバーや Simscape の Solver Configuration ブロックに反映したConfig情報はConfigList.xlsx、Simscape_ConfigList.xlsxとして添付する。
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3.4 見積計算速度
実時間の5倍速以下で設計予定
（10秒のシナリオをシミュレーション時間2秒以内で実現）
3.5 モデル秘匿化
mex64形式での秘匿状態（隠蔽）での納品とする。
3.6 参考ガイドライン
可読性・可視性の向上、安定した計算の実現を目的に以下のガイドラインを参考にする。
 PLANT MODELING GUIDELINES USING Matlab/Simulink Ver2.1（JMAAB）

### 3 要求機能と実現方法: 要求機能と実現方法 (Functional)
4 要求機能と実現方法
3
4
4.1 モデル化対象範囲
本モデルは図3車両モデル内の赤枠部に組込まれ使用される。
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図3.車両モデル概略
4.2 モデル要求機能
モータ、ジェネレータモデルにおける基本式を以下に示す。
両モデル共に出力信号はエネルギー保存式に基づき算出する。
𝑉 ∗𝐼_𝑡𝑒𝑚𝑝∗𝐸𝑓𝑓𝑖𝑐𝑖𝑒𝑛𝑐𝑦 = 𝑇_𝑡𝑎𝑟𝑔𝑒𝑡 ∗ 𝑊
V：モータ・ジェネレータ電圧、Itemp：モータ・ジェネレータ電流
T_target：要求モータトルク・要求ジェネレータトルク
W：モータ回転数・ジェネレータ回転数Efficiency：効率
符号の定義：
・各トルクは車両を前進させる方向を正として定義する。
・モータで消費する電流を正として定義する。
未考慮内容：
・フリクションは考慮せず。
・インバータによる電流脈動/トルク脈動は考慮せず。
・温度（雰囲気温度や自己発熱）によるモータ特性の変化は考慮せず。
1
2
3
3.1
3.2
1
2
3
3.1
3.2
4.3 機能実現方法
モータモデルの要求機能と実現方法
| 要求機能 | 実現方法 |
| --- | --- |
| トルク算出部： １．コントローラから指示されたトルクを車両動力として発生させる。 ２．モータトルク発生時消費される電流はモータ効率を考慮する。 ３．モータトルクには最大モータ電流値以上のトルクが出力しないように制限機能を設ける。 | Case1：力行側で電流制限がない場合 0≦𝐼_𝑡𝑒𝑚𝑝<𝐼_𝑚𝑎𝑥の時 𝑇 = 𝑇_𝑡𝑎𝑟𝑔𝑒𝑡 𝐼= 𝑇_𝑡𝑎𝑟𝑔𝑒𝑡∗𝑊/(𝑉 ∗ 𝐸𝑓𝑓𝑖𝑐𝑖𝑒𝑛𝑐𝑦) Case2：力行側で電流制限される場合、 𝐼𝑡𝑒𝑚𝑝≧𝐼_𝑚𝑎𝑥の時 𝑇 = 𝑉∗𝐼_𝑚𝑎𝑥∗𝐸𝑓𝑓𝑖𝑐𝑖𝑒𝑛𝑐𝑦/𝑊 𝐼=𝐼_𝑚𝑎𝑥 |
ジェネレータモデルの要求機能と実現方法
| 要求機能 | 実現方法 |
| --- | --- |
| 発電電流算出部： １．コントローラからの指示トルクをエンジン、車両動力から吸収し、電気エネルギーに変換、バッテリに貯蔵する。 ２．ジェネレータ電流算出時にはジェネレータ損失である効率を考慮する。 ３．発電電流は最大発電電流値以上の値が出力しないように制限機能を設ける。 | Case1：充電側で電流制限がない場合 𝐼𝑚𝑎𝑥<𝐼_𝑡𝑒𝑚𝑝<0時 𝑇 = 𝑇_𝑡𝑎𝑟𝑔𝑒𝑡 𝐼= 𝑇_𝑡𝑎𝑟𝑔𝑒𝑡∗𝑊∗𝐸𝑓𝑓𝑖𝑐𝑖𝑒𝑛𝑐𝑦/ 𝑉 Case2：充電側で電流制限される場合 𝐼𝑡𝑒𝑚𝑝≦− 𝐼_𝑚𝑎𝑥の時 𝑇 = 𝑉∗（−𝐼_𝑚𝑎𝑥）/ 𝑊∗𝐸𝑓𝑓𝑖𝑐𝑖𝑒𝑛𝑐𝑦 𝐼= −𝐼_𝑚𝑎𝑥 |
4.4 モデル外観イメージ
モータ・ジェネレータモデルの外観イメージを図4に示す。
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図4.モデル外観イメージ図
1
2
3
4
4.1
4.2
4.3
4.4
4.5 入出力信号及びパラメータ仕様
4.6
4.7
4.8
4.9
4.10
1
2
3
4
4.1
4.2
4.3
4.4
4.5
4.5.1 ノード
| ポート名 | 物理 ドメイン | Through/ Across | 内容 |
| --- | --- | --- | --- |
| R | 機械回転 | 回転数/トルク (rad/s / Nm) | モータ出力トルク |
| C | 機械回転 | 回転数/トルク (rad/s / Nm) | メカニカルリファレンス |
| P(+) | 電気 | 電圧/電流 (V / A) | モータ入力（正極） |
| N(-) | 電気 | 電圧/電流 (V / A) | モータ入力(負極) |
【補足】符号は車両を前進させる方向を正とする。

#### 4.5.2 モニタ変数: モニタ変数 (Functional)
4.5.2 モニタ変数
| 変数名 | 内容 | 範囲 | 初期値 | 単位 |
| --- | --- | --- | --- | --- |
| I | 電流 | -300 ~ 300 | 0 | A |
| I_temp | 指令電流 | -300 ~ 300 | 0 | A |
| V | 電圧 | 0 ~ 300 | 0 | V |
| T | モータ出力トルク | -300 ~ 300 | 0 | Nm |
| w | モータ回転数 | -1000 ~ 1000 | 0 | rad/sec |

#### 1 入力: 入力 (Functional)
4.5.3 入力
| ポート名 | 内容 | 範囲 | 初期値 | 単位 |
| --- | --- | --- | --- | --- |
| Target_Torque | 要求モータトルクor 要求ジェネレータトルク | -300 ~ 300 | 0 | Nm |
1
2
3
4
4.1
4.2
4.3
4.4
4.5
4.5.1
4.5.4 出力
なし

#### 4.5.5 パラメータ: パラメータ (Functional)
4.5.5 パラメータ
| 変数名 | 内容 | 範囲 | 単位 |
| --- | --- | --- | --- |
| Eff | モータ効率 | 0～1 | - |
| R | 巻線抵抗 | 0～1000 | Ω |

#### 4.5.6 データ型: データ型 (Functional)
4.5.6 データ型
doubleで設計
3
4
4.4
4.6 動作保証範囲
本モデルの動作保証範囲を以下に記載する。
1
2
3
4
4.1
4.2
4.3
4.4
4.5
4.6
4.6.1 モータ
モータモデルは以下の条件のみで動作を保証する。
・入力電流：0～300[A]
・入力電圧：0～300[V]
4.6.2 ジェネレータ
ジェネレータモデルは以下の条件のみで動作を保証する。
・入力トルク：0～300[Nm]
・入力回転数：0～10000[rpm]
4.7 その他関連情報
要求モデルは新規開発品な為、参考となるモデルなし。

### 5 検証: 検証 (Functional)
5 検証
5.1 検証シナリオと判断基準
・目標トルクをステップ時間1sec、振幅100Nで10秒間指令した際シミュレーション時間が2秒以下なこと
・指示されたモータトルクが0.1 %以内の誤差で出力されること。（0-5000 rpm/ 0-110 Nm ）
・モデルの特性や挙動が物理現象と定性的に合致していること
・ただし、指示トルクがモータの電流制限を超えた場合、電流制限応じたトルクに制限されること。
5.2 検証結果
TBD
3.
4.
5.
6 サポート要件
6.1 サポート内容
・初期導入オンサイトサポート（3日）
・エラー発生時のサポート（常時）
6.2 サポート期間
プロジェクトが完了する2020年6月末まで
6.3 問合せ先
メール：jmaab-pmwg@mathworks.com
TEL：xxxx - yyyy - zzzz
